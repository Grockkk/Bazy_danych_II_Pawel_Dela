FME workspace dodatkowe.fmw

Parameters:
- path = C:\Studia\T2019_KAR_WATERS.zip   # "" Wpisz sicieżkę do pliku do wysłania
- file = WATERS   # podaj nazwe warstwy

Creator
    GEOMTYPE = Geometry Object
    NUM = 1
    CREATED -> HTTPCaller
HTTPCaller
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api.mapbox.com/uploads/v1/pdela/credentials?access_token=sk.eyJ1IjoicGRlbGEiLCJhIjoiY2xkN2N0ZnkzMWkxNzNwbW1hcWVieXd3ZyJ9.gtSJlDOCRmjiEHZfcleZMg
    TRANSFER_TIMEOUT_LENGTH = 90
    UPLOAD_CONTENT_TYPE = Text (text/plain)
    UPLOAD_FILE = $(path)
    UPLOAD_TYPE = Upload From File
    USE_COOKIES = No
    VERIFY_SSL_CERTIFICATES = Yes
    -> AttributeCreator
AttributeCreator
    ATTR_TABLE = SET_TO upload = curl -X POST -H "Content-Type: application/json" -H "Cache-Control: no-cache" -d "{ \"url\": \"http://tilestream-tilesets-production.s3.amazonaws.com/06/_pending/8gjf3xpmznd265c0huage7dlc/pdela\", \"tileset\": \"pdela.Waters\", \"name\": \"$(file)\"}" https://api.mapbox.com/uploads/v1/pdela?access_token=sk.eyJ1IjoicGRlbGEiLCJhIjoiY2xkN2N0ZnkzMWkxNzNwbW1hcWVieXd3ZyJ9.gtSJlDOCRmjiEHZfcleZMg
    -> SystemCaller
SystemCaller
    CMD = @Value(upload)
    -> Inspector
Inspector
